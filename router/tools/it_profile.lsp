;;; Integration scenario for the profile architecture, run via acc_profile.py.
(load "D:/BLOCK/router/tools/it_scenario.lsp")

(defun it-count-block (name / ss) (setq ss (ssget "_X" (list (cons 2 name)))) (if ss (sslength ss) 0))

(defun it-profiles ()
  (ctr-ensure-layers)
  ;; DEFAULT profile: straight -> elbow (root D:\BLOCK blocks, bare names)
  (it-mkpath-p '((0.0 0.0) (3000.0 0.0) (3000.0 2000.0)) 300.0 "DEFAULT")
  ;; SCADA_BASIC profile: straight -> elbow (D:\BLOCK\DEFAULT blocks, aliased names)
  (it-mkpath-p '((0.0 5000.0) (3000.0 5000.0) (3000.0 7000.0)) 300.0 "SCADA_BASIC")
  ;; SCADA_BASIC: a Tee (config unconfirmed -> must not crash)
  (it-mkpath-p '((0.0 10000.0) (3000.0 10000.0) (6000.0 10000.0)) 300.0 "SCADA_BASIC")
  (it-mkpath-p '((3000.0 12000.0) (3000.0 10000.0)) 300.0 "SCADA_BASIC")
  ;; SCADA_BASIC: a Cross (must be REJECTED, profile does not support it)
  (it-mkpath-p '((0.0 20000.0) (3000.0 20000.0) (6000.0 20000.0)) 300.0 "SCADA_BASIC")
  (it-mkpath-p '((3000.0 22000.0) (3000.0 20000.0) (3000.0 18000.0)) 300.0 "SCADA_BASIC")
  (c:CTRAYUPDATE)
  (princ (strcat "\nPROFILE_CHECK bare-elbow-count="   (itoa (it-count-block "SCADA_TRAY_ELBOW"))
                 " basic-elbow-count=" (itoa (it-count-block "SCADA_BASIC$SCADA_TRAY_ELBOW"))
                 " basic-tee-count="   (itoa (it-count-block "SCADA_BASIC$SCADA_TRAY_TEE"))
                 " any-cross-count="   (itoa (+ (it-count-block "SCADA_TRAY_CROSS")
                                                 (it-count-block "SCADA_BASIC$SCADA_TRAY_CROSS")))))
  (princ (strcat "\nPROFILE_CHECK tray-total=" (itoa (it-count))))
  (princ))
(princ)
