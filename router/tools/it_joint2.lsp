(load "D:/BLOCK/router/tools/it_scenario.lsp")
(defun it-dump-lwpl-x (layer xlo xhi / ss i n en ed pts p mnx mny mxx mxy)
  (setq ss (ssget "_X" (list (cons 8 layer) (cons 0 "LWPOLYLINE,INSERT"))))
  (setq n (if ss (sslength ss) 0) i 0)
  (while (< i n)
    (setq en (ssname ss i) ed (entget en))
    (if (= (cdr (assoc 0 ed)) "INSERT")
      (princ (strcat "\nJINS " (cdr (assoc 2 ed)) " ip=" (vl-princ-to-string (cdr (assoc 10 ed)))
                     " rot=" (rtos (cdr (assoc 50 ed)) 2 4) " scale=" (rtos (cdr (assoc 41 ed)) 2 4)))
      (progn
        (setq pts nil)
        (foreach p ed (if (= (car p) 10) (setq pts (cons (cdr p) pts))))
        (if (and pts (>= (car (car pts)) xlo) (<= (car (car pts)) xhi))
          (progn
            (setq mnx (car (car pts)) mxx mnx mny (cadr (car pts)) mxy mny)
            (foreach p pts (setq mnx (min mnx (car p)) mxx (max mxx (car p))
                                 mny (min mny (cadr p)) mxy (max mxy (cadr p))))
            (princ (strcat "\nJPOLY " (rtos mnx 2 3) "," (rtos mny 2 3) ","
                           (rtos mxx 2 3) "," (rtos mxy 2 3)))))))
    (setq i (1+ i)))
  (princ))

(defun it-joint2 ()
  (ctr-ensure-layers)
  (it-mkpath-p (list (list 0.0 0.0) (list 3000.0 0.0) (list 3000.0 2000.0)) 300.0 "SCADA_BASIC")
  (c:CTRAYUPDATE)
  (it-dump-lwpl-x "SCADA-TRAY" 2000.0 2900.0)
  (princ "\n--- explode elbow only ---")
  (setq ss (ssget "_X" (list (cons 8 "SCADA-TRAY") (cons 0 "INSERT"))))
  (setq ss1 (ssadd (ssname ss 0) (ssadd)))
  (command "_.EXPLODE" ss1 "")
  (princ "\nEXPLODE-DONE")
  (it-dump-lwpl-x "SCADA-TRAY" 2000.0 2900.0)
  (princ))
(princ)
