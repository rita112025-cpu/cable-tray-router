;;; SCADA_V2 elbow join-delta measurement, run via acc_v2elbow.py
(load "D:/BLOCK/router/tools/it_scenario.lsp")

(defun it-dump-all3 (label / ss i n en ed pts p lay)
  (setq ss (ssget "_X" (list '(-4 . "<OR")
                             (cons 0 "LWPOLYLINE") (cons 0 "LINE") '(-4 . "OR>"))))
  (setq n (if ss (sslength ss) 0) i 0)
  (while (< i n)
    (setq en (ssname ss i) ed (entget en) pts nil lay (cdr (assoc 8 ed)))
    (foreach p ed (if (member (car p) (list 10 11)) (setq pts (cons (cdr p) pts))))
    (princ (strcat "\nV " label " " lay " " (cdr (assoc 5 ed)) " "))
    (foreach p pts (princ (strcat "(" (rtos (car p) 2 4) " " (rtos (cadr p) 2 4) ")")))
    (setq i (1+ i)))
  (princ))

(defun it-v2elbow (/ ss i n en ed)
  (ctr-ensure-layers)
  ;; W+N elbow at node (0,0), width = BLOCK_WIDTH exactly -> scale should be 1.0
  (it-mkpath-p (list (list 0.0 0.0) (list 3000.0 0.0) (list 3000.0 2000.0)) 622.93 "SCADA_V2")
  (c:CTU)
  (princ (strcat "\nOBJCOUNT-BEFORE=" (itoa (it-count))))
  (it-dump-all3 "BEFORE")
  (setq ss (ssget "_X" (list (cons 8 "SCADA-TRAY") (cons 0 "INSERT"))))
  (setq n (if ss (sslength ss) 0) i 0)
  (princ (strcat "\nFITTING-INSERT-COUNT=" (itoa n)))
  (while (< i n)
    (setq en (ssname ss i))
    (setq ed (entget en))
    (princ (strcat "\nINS " (cdr (assoc 2 ed)) " ip=(" (rtos (cadr (assoc 10 ed)) 2 4) " "
                   (rtos (caddr (assoc 10 ed)) 2 4) ") rot=" (rtos (cdr (assoc 50 ed)) 2 6)
                   " scale=" (rtos (cdr (assoc 41 ed)) 2 6)))
    (command "_.EXPLODE" (ssadd en (ssadd)))
    (setq i (1+ i)))
  (princ "\nEXPLODE-ALL-DONE")
  (it-dump-all3 "AFTER")
  (princ))
(princ)
